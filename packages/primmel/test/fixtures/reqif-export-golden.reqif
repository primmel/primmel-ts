# Test package

# Specification: Test package

## test-pkg: Test package (document)
A tiny export fixture.

## /req/scope: Scope requirements (heading)
- cross-reference -> /req/other

### /req/scope/alpha: Alpha (provision)
The widget shall frobnicate & pass <all> "checks".
- obj.modality: requirement
- obj.normativity: normative
- primmel.object-kind: requirement
- obj.clause-number: 5.2; 5.2.1
- primmel.verification-method: examination
- cross-reference -> /req/scope/beta
- cross-reference -> /req/scope/beta

### /req/scope/beta: Beta (provision)
The widget should glow.
- obj.modality: recommendation
- obj.normativity: normative
- primmel.object-kind: requirement
- obj.clause-number: 5.3

### /req/scope/gamma: Gamma (provision)
The widget may hum.
- obj.modality: permission
- obj.normativity: normative
- primmel.object-kind: requirement

## /req/other: Other requirements (heading)

## /req/orphan: Orphan (provision)
The widget shall stand alone.
- obj.modality: requirement
- obj.normativity: normative
- primmel.object-kind: requirement

## primmel:conformance-tests: Conformance tests (heading)

### /conf/scope-tests/alpha-check: Alpha check (provision)
Verify the widget frobnicates.
- obj.modality: undefined
- obj.normativity: normative
- primmel.object-kind: conformance-test
- cross-reference -> /req/scope/alpha
